Attribute VB_Name = "frmCAAPriHoleDescription"
Attribute VB_Base = "0{57304F0C-2F57-499F-8A7D-C0D6EBBB7E5F}{2A1EA45C-EE9C-4740-B0EE-10A08F114679}"
Attribute VB_GlobalNameSpace = False
Attribute VB_Creatable = False
Attribute VB_PredeclaredId = True
Attribute VB_Exposed = False
Attribute VB_TemplateDerived = False
Attribute VB_Customizable = False
Option Explicit

' COPYRIGTH DASSAULT SYSTEMES 2004

' ***********************************************************************
'   Purpose:      Changes hole description
'   Assumtions:   Looks for CAAPriHoleDescriptionCATvba.htm in the DocView
'   Author:
'   Languages:    VBA
'   Locales:      English
'   CATIA Level:  V5R13
' ***********************************************************************

Private oUnit As Double
 
Private Sub cmdOk_Click()

Dim oHole As Hole
Dim iRow As Long
Dim iHoleInSelection As Boolean
Dim oParameters As Parameters

' ------------
' Get the description you wish, by default pre-select the first description
' ------------
iRow = mfgDescription.RowSel
frmCAAPriHoleDescription.Hide
iHoleInSelection = True
' ------------
' Loop on the selection content, we expect to find a hole
' ------------
Do While iHoleInSelection = True
    iHoleInSelection = CatObjectExistsInSelection(oPartDocument.Selection, "CATIAHole", oHole)
    If iHoleInSelection = True Then
        ' ------------
        ' There is a hole object in the selection
        ' ------------
        ' Get the hole limit
        ' ------------
        Select Case mfgDescription.TextMatrix(iRow, 5)
            Case "UpToNext"
                oHole.BottomLimit.LimitMode = catUpThruNextLimit
                ' ------------
                ' Update the part when set the hole limit to "UpToNext"
                ' ------------
                oPartDocument.Part.Update
            Case Else
                oHole.BottomLimit.LimitMode = catOffsetLimit
                oHole.BottomLimit.Dimension.Value = CDbl(mfgDescription.TextMatrix(iRow, 5)) * oUnit
        End Select
        ' ------------
        ' Get the hole diameter and its tolerances
        ' ------------
        oHole.Diameter.Value = CDbl(mfgDescription.TextMatrix(iRow, 2))
        oHole.Diameter.MaximumTolerance = (CDbl(mfgDescription.TextMatrix(iRow, 3)) - CDbl(mfgDescription.TextMatrix(iRow, 2))) * oUnit
        oHole.Diameter.MinimumTolerance = (CDbl(mfgDescription.TextMatrix(iRow, 4)) - CDbl(mfgDescription.TextMatrix(iRow, 2))) * oUnit
        Set oParameters = oPartDocument.Part.Parameters.SubList(oHole, True)
        ' ------------
        ' Set the hole description parameter
        ' ------------
        If ParameterExists("Hole_Description", oParameters) = True Then
            oParameters.Item("Hole_Description").ValuateFromString (mfgDescription.TextMatrix(iRow, 0))
        Else
            oParameters.CreateString "Hole_Description", mfgDescription.TextMatrix(iRow, 0)
        End If
        ' ------------
        ' Get the hole type
        ' ------------
        Select Case mfgDescription.TextMatrix(iRow, 1)
            Case "Simple"
                oHole.Type = catSimpleHole
            Case "Counterbored"
                oHole.Type = catCounterboredHole
                oHole.HeadDiameter.Value = CDbl(mfgDescription.TextMatrix(iRow, 9)) * oUnit
                oHole.HeadDepth.Value = CDbl(mfgDescription.TextMatrix(iRow, 12)) * oUnit
                oHole.HeadDiameter.MaximumTolerance = (CDbl(mfgDescription.TextMatrix(iRow, 10)) - CDbl(mfgDescription.TextMatrix(iRow, 9))) * oUnit
                oHole.HeadDiameter.MinimumTolerance = (CDbl(mfgDescription.TextMatrix(iRow, 11)) - CDbl(mfgDescription.TextMatrix(iRow, 9))) * oUnit
        End Select
        ' ------------
        ' Get the hole thread definition
        ' ------------
        Select Case mfgDescription.TextMatrix(iRow, 6)
            Case "Yes"
                If oHole.Diameter.Value < oHole.ThreadDiameter.Value And oHole.BottomLimit.Dimension.Value > oHole.ThreadDepth.Value Then
                    ' ------------
                    ' Update the part when hole diameter is smaller than tread diameter
                    ' and hole limit is greater than thread depth, before apply new values
                    ' -----------
                    oPartDocument.Part.Update
                End If
                oHole.ThreadingMode = catThreadedHoleThreading
                oHole.ThreadDiameter.Value = CDbl(mfgDescription.TextMatrix(iRow, 7)) * oUnit
                oHole.ThreadDepth.Value = CDbl(mfgDescription.TextMatrix(iRow, 8)) * oUnit
            Case "No"
                oHole.ThreadingMode = catSmoothHoleThreading
        End Select
        ' ------------
        ' Update the part
        ' ------------
        oPartDocument.Part.Update
    End If
Loop

Unload Me
    
End Sub

Private Sub cmdCancel_Click()

' ------------
' Unload the form
' ------------
Unload Me

End Sub

Private Sub mfgDescription_Click()

End Sub

Private Sub UserForm_Initialize()

Dim oCATIAFileSys
Dim oFile As File
Dim oTextSteam As TextStream
Dim oUnit As Double
Dim oLine As String
Dim iArray() As String
Dim oRow As Long
Dim iDelimiter As String

' ------------
' The string as delimiter between input in the text file
' ------------
iDelimiter = "\\"
' ------------
' Get the CATIA file system
' ------------
Set oCATIAFileSys = CATIA.FileSystem
' ------------
' Get the file containing the hole descriptions
' ------------
Set oFile = oCATIAFileSys.GetFile(sDocPath & "\online\CAAScdPriUseCases\macros\CAAPriHoleDescription.txt")
' ------------
' Get the text stream
' ------------
Set oTextSteam = oFile.OpenAsTextStream("ForReading")
oLine = oTextSteam.ReadLine
Select Case oLine
    Case "Millimeter"
        oUnit = 1
    Case "Inch"
        oUnit = 25.4
End Select
oRow = 0
' ------------
' Read the hole descriptions
' ------------
Do While oTextSteam.AtEndOfStream = False
    oLine = oTextSteam.ReadLine
    iArray = Split(oLine, iDelimiter)
    For i = 0 To 12
        mfgDescription.TextMatrix(oRow, i) = iArray(i)
    Next i
    oRow = oRow + 1
Loop
oTextSteam.Close
cmdOk.Enabled = True

End Sub

Attribute VB_Name = "modCAAPriHoleDescription"
Option Explicit

' COPYRIGTH DASSAULT SYSTEMES 2004

' ***********************************************************************
'   Purpose:      Changes hole description
'   Assumptions:   Looks for CAAPriHoleDescriptionCATvba.htm in the DocView
'   Author:
'   Languages:    VBA
'   Locales:      English
'   CATIA Level:  V5R13

Public oPartDocument As PartDocument
Public i As Long
Public sDocPath As String

Sub CATMain()

' -----------------------------------------------------------
' Optional: allows to find the sample wherever it's installed
sDocPath = CATIA.SystemService.Environ("CATDocView")
If (Not CATIA.FileSystem.FolderExists(sDocPath)) Then
  Err.Raise 9999, , "No Doc Path Defined"
End If
' -----------------------------------------------------------

' ------------
' Get the part document
' ------------
Set oPartDocument = CATIA.ActiveDocument
' ------------
' Test the selection content
' ------------
If oPartDocument.Selection.Count = 0 Then
    ' ------------
    ' The selection content is empty, the macro ends
    ' ------------
    MsgBox "Please select the holes you wish to transform before running the macro.", vbOKOnly, "Warning"
Else
    ' ------------
    ' The selection content is not empty
    ' Show the dialog box
    ' ------------
    frmCAAPriHoleDescription.Show
End If

End Sub

Public Function CatObjectExistsInSelection(CatSelection As Selection, CatObjectName As String, CatObject As Object) As Boolean

On Error Resume Next
Set CatObject = CatSelection.FindObject(CatObjectName)
CatObjectExistsInSelection = (Err.Number = 0)
Err.Clear

End Function

Public Function ParameterExists(ItemIndex As String, ItemCollection As Object) As Boolean

Dim TmpItem As Variant
On Error Resume Next
Set TmpItem = ItemCollection.Item(ItemIndex)
ParameterExists = (Err.Number = 0)
Err.Clear
    
End Function
