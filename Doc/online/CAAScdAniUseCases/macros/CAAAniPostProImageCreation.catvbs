' COPYRIGHT DASSAULT SYSTEMES 2000

' ***********************************************************************
'   Purpose:      To create demonstrate how images are created
'                 under analysis sets and restraints.
'   Assumtions:   
'   Author:       bmw
'   Languages:    VBScript
'   Locales:      English 
'   CATIA Level:  V5R16
' ***********************************************************************

Sub CATMain()
' ----------------------------------------------------------- 
' Optional: allows to find the sample wherever it's installed
  sDocPath=CATIA.SystemService.Environ("CATDocView")

    If (Not CATIA.FileSystem.FolderExists(sDocPath)) Then
      Err.Raise 9999,,"No Doc Path Defined"
    End If
' ----------------------------------------------------------- 


' Open the CATAnalysis Document
sFilePath = CATIA.FileSystem.ConcatenatePaths(sDocPath, "online\CAAScdAniUseCases\samples\Cube_R13_Freq.CATAnalysis")
Set oAnalysisDocument = CATIA.Documents.Open(sFilePath)

'Set oAnalysisDocument = CATIA.ActiveDocument

Set oAnalysisManager = oAnalysisDocument.Analysis

Set oAnalysisModels = oAnalysisManager.AnalysisModels

Set oAnalysisModel = oAnalysisModels.Item(1)

Set oAnalysisCases = oAnalysisModel.AnalysisCases

Set oAnalysisCase = oAnalysisCases.Item(1)

Set oAnalysisSets = oAnalysisCase.AnalysisSets

Set oAnalysisSet = oAnalysisSets.Item("Frequency Case Solution.1", catAnalysisSetSearchAll)

Set oAnalysisImages = oAnalysisSet.AnalysisImages

'Image creation  under Frequency Case Solution.1 imagename=Disp_Symbol,  hide existing image=no, showmesh = no, duplicate=yes 
'=================================================================================

Set analysisImage1 = oAnalysisImages.Add("Disp_Symbol", False, False, True)

'Image creation  under Frequency Case Solution.1 imagename=Mesh_Deformed,  hide existing image=yes, showmesh = no, duplicate=yes 
'====================================================================================

Set analysisImage2 = oAnalysisImages.Add("Mesh_Deformed", True, False, True)

Set analysisSet2 = oAnalysisSets.Item("Restraints.1", catAnalysisSetSearchAll)

Set analysisEntities1 = analysisSet2.AnalysisEntities

Set analysisEntity1 = analysisEntities1.Item(1)

Set analysisImages2 = analysisEntity1.AnalysisImages

'Image creation  under Clamp imagename=Restraint,  hide existing image=yes, showmesh = yes, duplicate=no 
'=================================================================================

Set analysisImage3 = analysisImages2.Add("Restraint", True, True, False)

End Sub
