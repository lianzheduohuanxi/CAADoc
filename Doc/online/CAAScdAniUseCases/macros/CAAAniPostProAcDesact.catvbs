' COPYRIGHT DASSAULT SYSTEMES 2000

' ***********************************************************************
'   Purpose:      To demonstrate activation and deactivation of image
'   Assumtions:   displacement symbol image exists in the document
'   Author:       bmw
'   Languages:    VBScript
'   Locales:      English 
'   CATIA Level:  V5R16
' ***********************************************************************

Sub CATMain()
' ----------------------------------------------------------- 
' Optional: allows to find the sample wherever it's installed
  sDocPath=CATIA.SystemService.Environ("CATDocView")

    If (Not CATIA.FileSystem.FolderExists(sDocPath)) Then
      Err.Raise 9999,,"No Doc Path Defined"
    End If
' ----------------------------------------------------------- 


' Open the CATAnalysis Document
sFilePath = CATIA.FileSystem.ConcatenatePaths(sDocPath, "online\CAAScdAniUseCases\samples\Cube_R13_Freq.CATAnalysis")
Set oAnalysisDocument = CATIA.Documents.Open(sFilePath)

Set oAnalysisManager = oAnalysisDocument.Analysis

Set oAnalysisModels = oAnalysisManager.AnalysisModels

Set oAnalysisModel = oAnalysisModels.Item(1)

Set oAnalysisCases = oAnalysisModel.AnalysisCases

Set oAnalysisCase = oAnalysisCases.Item(1)

Set oAnalysisSets = oAnalysisCase.AnalysisSets

Set oAnalysisSet = oAnalysisSets.Item("Frequency Case Solution.1", catAnalysisSetSearchAll)

Set analysisImages1 = oAnalysisSet.AnalysisImages

'activation of an  image
'==============
'we search image Disp_Symbol
Set oAnalysisImage = analysisImages1.Item("Disp_Symbol")

'we Activate the image
oAnalysisImage.SetActivationStatus true

'we update the  image
oAnalysisImage.Update

'deactivation of an  image
'===============
'we deactivate the image
oAnalysisImage.SetActivationStatus false

'we update the  image
oAnalysisImage.Update

End Sub
